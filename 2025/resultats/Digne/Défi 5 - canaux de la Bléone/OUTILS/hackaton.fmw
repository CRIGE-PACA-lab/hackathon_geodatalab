FME workspace hackaton.fmw

Parameters:
- SourceDataset_SHAPEFILE = C:\Users\m25030786\TRAVAIL\Hackaton\DATA\CANAUX\gravitaire_bleone.shp   # Shapefile(s) Esri source 
- DestDataset_SHAPEFILE = C:\Users\m25030786\TRAVAIL\Hackaton\DATA\CANAUX   # Répertoire destination Shapefile Esri 
- SourceDataset_SHAPEFILE_2 = ""D:\Hackaton\DATA\canauxsec.shp" "D:\Hackaton\DATA\canauxsout.shp""   # Shapefile(s) Esri source 

Readers:
- SHAPEFILE_1: SHAPEFILE from $(SourceDataset_SHAPEFILE)
- SHAPEFILE_3: SHAPEFILE from $(SourceDataset_SHAPEFILE_2)

Writers:
- SHAPEFILE_2: SHAPEFILE to $(DestDataset_SHAPEFILE)

gravitaire_bleone_v3 (writer SHAPEFILE_2)
    attributes: canal_nom varchar(150), canal_code varchar(15), asa_nom varchar(150), asa_code varchar(15), code_type varchar(2), lib_type varchar(150), comment varchar(150)

Bookmark: BD HYDRA 2015
gravitaire_bleone (reader SHAPEFILE_1)
    attributes: NOM_TRUCTU varchar(50), NOM_CANAL varchar(50), TYPE_CANAL varchar(2), CODE_HYDRA varchar(30)
    -> AttributeRenamer
Note: Renommer les champs (casse et cohérence avec la couche des ASA)
AttributeRenamer
    ATTR_TABLE:
      RENAME_SET_DEFAULT CODE_HYDRA > canal_code
      RENAME_SET_DEFAULT NOM_CANAL > canal_nom
      RENAME_SET_DEFAULT NOM_TRUCTU > asa_nom
      RENAME_SET_DEFAULT TYPE_CANAL > canal_type
    KEEP_RENAMED_ONLY = no
    MISSING_INPUT_ATTRS = REMOVE
    -> AttributeManager
Note: Rajout d'un champ "lib_type"
AttributeManager
    ATTR_TABLE:
      SET_TO asa_code (varchar(15))
      RENAME_SET_VALUE canal_type > code_type (varchar(2))
      SET_TO lib_type (varchar(150)) = primaire
      SET_TO comment (varchar(13)) = BD HYDRA 2015
    -> gravitaire_bleone_v3 (writer SHAPEFILE_2)

Bookmark: BUT GB 2023
canauxsec (reader SHAPEFILE_3)
    attributes: ID varchar(24), PREC_PLANI float, PREC_ALTI float, ARTIF varchar(3), FICTIF varchar(3), FRANCHISST varchar(10), NOM varchar(70), POS_SOL short, REGIME varchar(12), Z_INI float, Z_FIN float
    -> AttributeManager_3
Note: Suppression des champs inutiles + ajout d'un champ "lib_type"
AttributeManager_3
    ATTR_TABLE:
      REMOVE ID (varchar(24))
      REMOVE PREC_PLANI (real32)
      REMOVE PREC_ALTI (real32)
      REMOVE ARTIF (varchar(3))
      REMOVE FICTIF (varchar(3))
      REMOVE FRANCHISST (varchar(10))
      REMOVE NOM (varchar(70))
      REMOVE POS_SOL (int16)
      REMOVE REGIME (varchar(12))
      REMOVE Z_INI (real32)
      REMOVE Z_FIN (real32)
      SET_TO lib_type (varchar(50)) = secondaire
    -> AttributeCreator
canauxsout (reader SHAPEFILE_3)
    attributes: ID varchar(24), PREC_PLANI float, PREC_ALTI float, ARTIF varchar(3), FICTIF varchar(3), FRANCHISST varchar(10), NOM varchar(70), POS_SOL short, REGIME varchar(12), Z_INI float, Z_FIN float
    -> AttributeManager_2
AttributeManager_2
    ATTR_TABLE:
      REMOVE ID (varchar(24))
      REMOVE PREC_PLANI (real32)
      REMOVE PREC_ALTI (real32)
      REMOVE ARTIF (varchar(3))
      REMOVE FICTIF (varchar(3))
      REMOVE FRANCHISST (varchar(10))
      REMOVE NOM (varchar(70))
      REMOVE POS_SOL (int16)
      REMOVE REGIME (varchar(12))
      REMOVE Z_INI (real32)
      REMOVE Z_FIN (real32)
      SET_TO lib_type (varchar(50)) = souterrain
    -> AttributeCreator
Note: ajout d'un champ commentaire "comment"
AttributeCreator
    ATTR_TABLE = SET_TO comment (varchar(11)) = BUT GB 2023
    -> gravitaire_bleone_v3 (writer SHAPEFILE_2)
