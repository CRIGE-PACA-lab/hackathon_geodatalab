FME workspace HACKATON.fmw

Parameters:
- SourceDataset_SHAPEFILE = C:\Users\ronal\OneDrive\Bureau\ETUDE\Master HYDROPOTECH\HACKATON\Aeroport.shp   # Source Esri Shapefile(s)
- SourceDataset_SHAPEFILE_5 = ""C:\Users\ronal\OneDrive\Bureau\ETUDE\Master HYDROPOTECH\HACKATON\argiles Nice.shp" "C:\Users\ronal\OneDrive\Bureau\ETUDE\Master HYDROPOTECH\HACKATON\Batiment.shp""   # Source Esri Shapefile(s)
- SourceDataset_SHAPEFILE_11 = ""C:\Users\ronal\OneDrive\Bureau\ETUDE\Master HYDROPOTECH\HACKATON\Culture.shp" "C:\Users\ronal\OneDrive\Bureau\ETUDE\Master HYDROPOTECH\HACKATON\dce_localisation_Nice.shp" "C:\Users\ronal\OneDrive\Bureau\ETUDE\Master HYDROPOTECH\HACKATON\Foret Dense.shp" "C:\Users\ronal\OneDrive\Bureau\ETUDE\Master HYDROPOTECH\HACKATON\Foret Dense2.shp" "C:\Users\ronal\OneDrive\Bureau\ETUDE\Master HYDROPOTECH\HACKATON\Foret Faible.shp""   # Source Esri Shapefile(s)
- SourceDataset_SHAPEFILE_9 = ""C:\Users\ronal\OneDrive\Bureau\ETUDE\Master HYDROPOTECH\HACKATON\St_Laurent_et_Nice.shp" "C:\Users\ronal\OneDrive\Bureau\ETUDE\Master HYDROPOTECH\HACKATON\Trottoir  Commune.shp" "C:\Users\ronal\OneDrive\Bureau\ETUDE\Master HYDROPOTECH\HACKATON\Vege_dense.shp" "C:\Users\ronal\OneDrive\Bureau\ETUDE\Master HYDROPOTECH\HACKATON\zone_humide.shp""   # Source Esri Shapefile(s)
- DestDataset_SHAPEFILE = C:\Users\ronal\OneDrive\Bureau\ETUDE\Master HYDROPOTECH\HACKATON\EXp   # Destination Esri Shapefile Folder
- SourceDataset_SHAPEFILE_13 = C:\Users\ronal\OneDrive\Bureau\ETUDE\Master HYDROPOTECH\HACKATON\argiles Nice.shp   # Source Esri Shapefile(s)
- SourceDataset_SHAPEFILE_10 = C:\Users\ronal\OneDrive\Bureau\ETUDE\Master HYDROPOTECH\HACKATON\ROUTE2.shp   # Source Esri Shapefile(s)
- SourceDataset_SHAPEFILE_12 = ""C:\Users\ronal\OneDrive\Bureau\ETUDE\Master HYDROPOTECH\HACKATON\DH_ZSC_Clip1.shp" "C:\Users\ronal\OneDrive\Bureau\ETUDE\Master HYDROPOTECH\HACKATON\DO_ZPS_Clip1.shp" "C:\Users\ronal\OneDrive\Bureau\ETUDE\Master HYDROPOTECH\HACKATON\N_ENP_APB_S_R93_Clip1.shp""   # Source Esri Shapefile(s)

Readers:
- SHAPEFILE_1: SHAPEFILE from $(SourceDataset_SHAPEFILE)
- SHAPEFILE_2: SHAPEFILE from $(SourceDataset_SHAPEFILE_5)
- SHAPEFILE_3: SHAPEFILE from $(SourceDataset_SHAPEFILE_11)
- SHAPEFILE_4: SHAPEFILE from $(SourceDataset_SHAPEFILE_9)
- SHAPEFILE_6: SHAPEFILE from $(SourceDataset_SHAPEFILE_13)
- SHAPEFILE_7: SHAPEFILE from $(SourceDataset_SHAPEFILE_10)
- SHAPEFILE_8: SHAPEFILE from $(SourceDataset_SHAPEFILE_12)

Writers:
- SHAPEFILE_5: SHAPEFILE to $(DestDataset_SHAPEFILE)

N_ENP_APB_S_R93_Clip1 (reader SHAPEFILE_8)
    attributes: id_local varchar(80), id_mnhn varchar(80), nom_site varchar(93), date_crea varchar(80), modif_adm date, modif_geo date, url_fiche varchar(80), surf_off double, acte_deb varchar(80), acte_fin varchar(80), gest_site varchar(80), operateur varchar(80), precision varchar(80), src_geom varchar(80), src_annee varchar(80), marin varchar(80), p1_nature varchar(80), p2_culture varchar(80), p3_paysage varchar(80), p4_geologi varchar(80), p5_speleo varchar(80), p6_archeo varchar(80), p7_paleob varchar(80), p8_anthrop varchar(80), p9_science varchar(80), p10_public varchar(80), p11_dd varchar(80), p12_autre varchar(80), proced varchar(80), s_sig_ha double,
      motif_prot varchar(80), comment varchar(99), d_att_maj varchar(80), d_cart_pdf varchar(80), couche varchar(80), url_texte varchar(89), gid double, Shape_Leng double, Shape_Area double, NOTE long
    -> AttributeRenamer_13
AttributeRenamer_13
    ATTR_TABLE = RENAME_SET_DEFAULT NOTE > Z1
    KEEP_RENAMED_ONLY = no
    MISSING_INPUT_ATTRS = REMOVE
    -> AttributeKeeper_13
AttributeKeeper_13
    CREATE_BULK_MODE_FEATURES = NO
    KEEP_ATTRS = Z1
    -> AreaOnAreaOverlayer [AREA]
DH_ZSC_Clip1 (reader SHAPEFILE_8)
    attributes: sitecode varchar(80), sitename varchar(82), nom_usuel varchar(80), avancement varchar(80), s_sig_ha double, r_biogeo varchar(80), d_prop_ce date, d_list_alp date, d_list_med date, d_desig_am date, docob varchar(80), operateur varchar(80), animateur varchar(80), comment varchar(93), lien_inv varchar(80), source varchar(80), echel_num varchar(80), d_num_maj date, d_att_maj date, couche varchar(80), url_fiche varchar(80), url_docob varchar(80), url_texte varchar(88), gid double, Shape_Leng double, Shape_Area double, NOTE long
    -> AttributeRenamer_15
AttributeRenamer_15
    ATTR_TABLE = RENAME_SET_DEFAULT NOTE > Z2
    KEEP_RENAMED_ONLY = no
    MISSING_INPUT_ATTRS = REMOVE
    -> AttributeKeeper_15
AttributeKeeper_15
    CREATE_BULK_MODE_FEATURES = NO
    KEEP_ATTRS = Z2
    -> AreaOnAreaOverlayer [AREA]
DO_ZPS_Clip1 (reader SHAPEFILE_8)
    attributes: sitecode varchar(80), sitename varchar(80), nom_usuel varchar(80), s_sig_ha double, d_desig_am varchar(80), d_notif_ce varchar(80), docob varchar(80), operateur varchar(80), animateur varchar(84), comment varchar(98), lien_inv varchar(80), source varchar(80), echel_num varchar(80), d_num_maj varchar(80), d_att_maj varchar(80), couche varchar(80), url_fiche varchar(80), url_docob varchar(80), url_texte varchar(88), gid double, Shape_Leng double, Shape_Area double, NOTE long
    -> AttributeRenamer_14
AttributeRenamer_14
    ATTR_TABLE = RENAME_SET_DEFAULT NOTE > Z3
    KEEP_RENAMED_ONLY = no
    MISSING_INPUT_ATTRS = REMOVE
    -> AttributeKeeper_14
AttributeKeeper_14
    CREATE_BULK_MODE_FEATURES = NO
    KEEP_ATTRS = Z3
    -> AreaOnAreaOverlayer [AREA]
ROUTE2 (reader SHAPEFILE_7)
    attributes: Desimper varchar(200), AERO number(11,0), ARGILE number(11,0), BAT number(11,0), CULT number(11,0), DCE number(11,0), F02 number(11,0), F03 number(11,0), ETUDE number(11,0), TROT number(11,0), VEGE number(11,0), ZH number(11,0), Q__overlap number(31,15), PENTE float, ZONE varchar(254), ROUTE varchar(254), ZONE ECOLO varchar(254), ZONE impo varchar(10), NOTE long
    -> AttributeRenamer_12
AttributeRenamer_12
    ATTR_TABLE = RENAME_SET_DEFAULT NOTE > ROUTE
    KEEP_RENAMED_ONLY = no
    MISSING_INPUT_ATTRS = REMOVE
    -> AttributeKeeper_12
AttributeKeeper_12
    CREATE_BULK_MODE_FEATURES = NO
    KEEP_ATTRS = AERO,ROUTE
    -> AreaOnAreaOverlayer [AREA]
Aeroport (reader SHAPEFILE_1)
    attributes: ID varchar(24), CATEGORIE varchar(14), NATURE varchar(10), USAGE varchar(18), TOPONYME varchar(127), STATUT_TOP varchar(10), FICTIF varchar(3), ETAT varchar(15), DATE_CREAT varchar(19), DATE_MAJ varchar(19), DATE_APP date, DATE_CONF date, SOURCE varchar(127), ID_SOURCE varchar(254), ACQU_PLANI varchar(32), PREC_PLANI float, ALTITUDE float, CODE_ICAO varchar(4), CODE_IATA varchar(3), NOTE long
    -> AttributeRenamer
AttributeRenamer
    ATTR_TABLE = RENAME_SET_DEFAULT NOTE > AERO
    KEEP_RENAMED_ONLY = no
    MISSING_INPUT_ATTRS = REMOVE
    -> AttributeKeeper
AttributeKeeper
    CREATE_BULK_MODE_FEATURES = NO
    KEEP_ATTRS = AERO
    -> AreaOnAreaOverlayer [AREA]
argiles Nice (reader SHAPEFILE_6)
    attributes: NOM_COM varchar(45), CODE_DEP varchar(2), CODE_INSEE varchar(5), dpt varchar(2), niveau long, alea varchar(80), NOTE long
    -> AttributeRenamer_2
AttributeRenamer_2
    ATTR_TABLE = RENAME_SET_DEFAULT NOTE > ARGILE
    KEEP_RENAMED_ONLY = no
    MISSING_INPUT_ATTRS = REMOVE
    -> AttributeKeeper_4
AttributeKeeper_4
    CREATE_BULK_MODE_FEATURES = NO
    KEEP_ATTRS = ARGILE
    -> AreaOnAreaOverlayer [AREA]
Batiment (reader SHAPEFILE_2)
    attributes: ID varchar(24), NATURE varchar(19), NAT_DETAIL varchar(36), TOPONYME varchar(127), STATUT_TOP varchar(10), IMPORTANCE varchar(1), ETAT varchar(15), DATE_CREAT varchar(19), DATE_MAJ varchar(19), DATE_APP date, DATE_CONF date, SOURCE varchar(127), ID_SOURCE varchar(254), ACQU_PLANI varchar(32), PREC_PLANI float, ACQU_ALTI varchar(30), PREC_ALTI float, ID_2 varchar(24), NATURE_2 varchar(34), USAGE1 varchar(22), USAGE2 varchar(22), LEGER varchar(3), ETAT_2 varchar(15), DATE_CRE_1 varchar(19), DATE_MAJ_2 varchar(19), DATE_APP_2 date, DATE_CONF_ date, SOURCE_2 varchar(127), ID_SOURCE_ varchar(254), ACQU_PLA_1 varchar(32),
      ACQU_ALTI_ varchar(30), PREC_PLA_1 float, PREC_ALTI_ float, NB_LOGTS short, NB_ETAGES short, MAT_MURS varchar(2), MAT_TOITS varchar(2), HAUTEUR float, Z_MIN_SOL float, Z_MIN_TOIT float, Z_MAX_TOIT float, Z_MAX_SOL float, ORIGIN_BAT varchar(18), APP_FF varchar(32), IDS_RNB varchar(254), ID_3 varchar(24), NATURE_3 varchar(26), NAT_DETA_1 varchar(27), ETAT_3 varchar(15), DATE_CRE_2 varchar(19), DATE_MAJ_3 varchar(19), DATE_APP_3 date, DATE_CON_1 date, SOURCE_3 varchar(127), ID_SOURC_1 varchar(254), ACQU_PLA_2 varchar(32), PREC_PLA_2 float, ACQU_ALT_1 varchar(30), PREC_ALT_1 float, NOTE long,
      Surface float
    -> AttributeRenamer_3
AttributeRenamer_3
    ATTR_TABLE = RENAME_SET_DEFAULT NOTE > BAT
    KEEP_RENAMED_ONLY = no
    MISSING_INPUT_ATTRS = REMOVE
    -> AttributeKeeper_2
AttributeKeeper_2
    CREATE_BULK_MODE_FEATURES = NO
    KEEP_ATTRS = BAT
    -> AreaOnAreaOverlayer [AREA]
Culture (reader SHAPEFILE_3)
    attributes: ID varchar(24), DATE_APP date, DATE_CONF date, ACQU_PLANI varchar(32), PREC_PLANI float, NATURE varchar(28), SOURCE varchar(127), ID_SOURCE varchar(254), DATE_CREAT varchar(19), DATE_MAJ varchar(19), NOTE long
    -> AttributeRenamer_4
AttributeRenamer_4
    ATTR_TABLE = RENAME_SET_DEFAULT NOTE > CULT
    KEEP_RENAMED_ONLY = no
    MISSING_INPUT_ATTRS = REMOVE
    -> AttributeKeeper_3
AttributeKeeper_3
    CREATE_BULK_MODE_FEATURES = NO
    KEEP_ATTRS = CULT
    -> AreaOnAreaOverlayer [AREA]
dce_localisation_Nice (reader SHAPEFILE_3)
    attributes: fid number(20,0), datimport date, pa_type varchar(80), eu_cd_pa varchar(80), est_ref long, id_tri varchar(80), id long, NOTE long
    -> AttributeRenamer_5
AttributeRenamer_5
    ATTR_TABLE = RENAME_SET_DEFAULT NOTE > DCE
    KEEP_RENAMED_ONLY = no
    MISSING_INPUT_ATTRS = REMOVE
    -> AttributeKeeper_5
AttributeKeeper_5
    CREATE_BULK_MODE_FEATURES = NO
    KEEP_ATTRS = DCE
    -> AreaOnAreaOverlayer [AREA]
Foret Dense2 (reader SHAPEFILE_3)
    attributes: ID varchar(24), DATE_APP date, DATE_CONF date, ACQU_PLANI varchar(32), PREC_PLANI float, NATURE varchar(28), SOURCE varchar(127), ID_SOURCE varchar(254), DATE_CREAT varchar(19), DATE_MAJ varchar(19), NOTE long
    -> AttributeRenamer_6
AttributeRenamer_6
    ATTR_TABLE = RENAME_SET_DEFAULT NOTE > F02
    KEEP_RENAMED_ONLY = no
    MISSING_INPUT_ATTRS = REMOVE
    -> AttributeKeeper_6
AttributeKeeper_6
    CREATE_BULK_MODE_FEATURES = NO
    KEEP_ATTRS = F02
    -> AreaOnAreaOverlayer [AREA]
Foret Faible (reader SHAPEFILE_3)
    attributes: ID varchar(24), DATE_APP date, DATE_CONF date, ACQU_PLANI varchar(32), PREC_PLANI float, NATURE varchar(28), SOURCE varchar(127), ID_SOURCE varchar(254), DATE_CREAT varchar(19), DATE_MAJ varchar(19), NOTE long
    -> AttributeRenamer_7
AttributeRenamer_7
    ATTR_TABLE = RENAME_SET_DEFAULT NOTE > F03
    KEEP_RENAMED_ONLY = no
    MISSING_INPUT_ATTRS = REMOVE
    -> AttributeKeeper_7
AttributeKeeper_7
    CREATE_BULK_MODE_FEATURES = NO
    KEEP_ATTRS = F03
    -> AreaOnAreaOverlayer [AREA]
St_Laurent_et_Nice (reader SHAPEFILE_4)
    attributes: NOM_COM varchar(45), CODE_DEP varchar(2), CODE_INSEE varchar(5), NOTE long, Pente float, Type de ro varchar(254), Type de zo varchar(254), PP varchar(254)
    -> AttributeRenamer_8
AttributeRenamer_8
    ATTR_TABLE = RENAME_SET_DEFAULT NOTE > ETUDE
    KEEP_RENAMED_ONLY = no
    MISSING_INPUT_ATTRS = REMOVE
    -> AttributeKeeper_8
AttributeKeeper_8
    CREATE_BULK_MODE_FEATURES = NO
    KEEP_ATTRS = ETUDE
    -> AreaOnAreaOverlayer [AREA]
Trottoir Commune (reader SHAPEFILE_4)
    attributes: osm_id number(18,0), name varchar(80), amenity varchar(80), hstore_to_ varchar(254), wheelchair varchar(80), NOTE long
    -> AttributeRenamer_9
AttributeRenamer_9
    ATTR_TABLE = RENAME_SET_DEFAULT NOTE > TROT
    KEEP_RENAMED_ONLY = no
    MISSING_INPUT_ATTRS = REMOVE
    -> AttributeKeeper_9
AttributeKeeper_9
    CREATE_BULK_MODE_FEATURES = NO
    KEEP_ATTRS = TROT
    -> AreaOnAreaOverlayer [AREA]
Vege_dense (reader SHAPEFILE_4)
    attributes: ID varchar(24), DATE_APP date, DATE_CONF date, ACQU_PLANI varchar(32), PREC_PLANI float, NATURE varchar(28), SOURCE varchar(127), ID_SOURCE varchar(254), DATE_CREAT varchar(19), DATE_MAJ varchar(19), NOTE long
    -> AttributeRenamer_10
AttributeRenamer_10
    ATTR_TABLE = RENAME_SET_DEFAULT NOTE > VEGE
    KEEP_RENAMED_ONLY = no
    MISSING_INPUT_ATTRS = REMOVE
    -> AttributeKeeper_10
AttributeKeeper_10
    CREATE_BULK_MODE_FEATURES = NO
    KEEP_ATTRS = VEGE
    -> AreaOnAreaOverlayer [AREA]
zone_humide (reader SHAPEFILE_4)
    attributes: gid number(19,0), id long, date_mod varchar(8), code varchar(254), site varchar(254), sdage varchar(254), surf_m2 double, cod_ssbv varchar(254), lib_ssbv varchar(254), date_crea varchar(8), org_crea varchar(254), cr_delim varchar(254), org_mod varchar(254), moa varchar(254), an_crea long, aut_crea varchar(254), aut_mod varchar(254), ech_num double, ref varchar(254), NOTE long
    -> AttributeRenamer_11
AttributeRenamer_11
    ATTR_TABLE = RENAME_SET_DEFAULT NOTE > ZH
    KEEP_RENAMED_ONLY = no
    MISSING_INPUT_ATTRS = REMOVE
    -> AttributeKeeper_11
AttributeKeeper_11
    CREATE_BULK_MODE_FEATURES = NO
    KEEP_ATTRS = ZH
    -> AreaOnAreaOverlayer [AREA]
AreaOnAreaOverlayer
    ACCUM_ATTRS = ALL
    CLEANING_TOLERANCE_LOOKUP = AUTO
    CONNECT_Z_MODE_LOOKUP = FIRST_WINS
    DEAGGREGATE_INPUT = Yes
    OVC_ATTR = _overlaps
    ACCUM_ATTRS_NAME = Merge Incoming Attributes
    CLEANING_TOLERANCE = Automatic
    CONNECT_Z_MODE = First Wins
    AREA -> AttributeCreator
    <REJECTED> -> Junction
AttributeCreator
    ATTR_TABLE = SET_TO Desimper (varchar(200)) = FME_CONDITIONAL:DEFAULT_VALUE'OUI'BOOL_OP;OR;COMPOSITE_TEST;1 OR 2 OR 3 OR 4 OR 5 OR 6 OR 7 OR 8 OR 9 OR 10 OR 11;TEST @Value(AERO) = 2;TEST @Value(ARGILE) = 2;TEST @Value(DCE) = 2;TEST @Value(ZH) = 2;TEST @Value(BAT) = 2;TEST @Value(CULT) = 2;TEST @Value(F02) = 1;TEST @Value(F03) = 2;TEST @Value(Z1) = 2;TEST @Value(Z2) = 2;TEST @Value(Z3) = 2'NON'BOOL_OP;OR;COMPOSITE_TEST;1;TEST @Value(ROUTE) = 4'Etude complémentaire 'FME_NUM_CONDITIONS3___
    -> HackatonFINAL (writer SHAPEFILE_5)
HackatonFINAL (writer SHAPEFILE_5)
    attributes: Desimper varchar(200), AERO long, ARGILE long, BAT long, CULT long, DCE long, F02 long, F03 long, ETUDE long, TROT long, VEGE long, ZH long, ROUTE long, Z1 long, Z3 long, Z2 long, Q__overlap double
Junction
